-- This MIB Generated by the JBoss MIB Generator

SNMP-SERVLET-MIB DEFINITIONS ::=BEGIN

IMPORTS
	OBJECT-TYPE,
	NOTIFICATION-TYPE,
	Counter32,
	Gauge32,
	Counter64,
	TimeTicks
		FROM SNMPv2-SMI
	DisplayString,
	TruthValue
		FROM SNMPv2-TC;

snmpTestTraps		OBJECT IDENTIFIER ::= { 1 3 6 1 4 1 2312 100 10 11 6 }
snmpTestObjects		OBJECT IDENTIFIER ::= { 1 3 6 1 4 1 2312 100 10 11 }

message OBJECT-TYPE
	SYNTAX OCTET STRING (SIZE(0..255))
	ACCESS read-write
	STATUS current
	DESCRIPTION 
		""
::= { snmpTestObjects 1 }

count OBJECT-TYPE
	SYNTAX OCTET STRING (SIZE(0..255))
	ACCESS read-only
	STATUS current
	DESCRIPTION 
		""
::= { snmpTestObjects 2 }

jbossJmxNotificationStartTime OBJECT-TYPE
	SYNTAX OctetString
	ACCESS not-accessible
	STATUS current
	DESCRIPTION 
		""
::= { snmpTestObjects 1 }

snmpTestNotification NOTIFICATION-TYPE
	OBJECTS {
		message
		}
	STATUS current
	DESCRIPTION 
		""
::= { snmpTestTraps 10 }

messageHistoryTable OBJECT-TYPE
	SYNTAX	SEQUENCE OF MessageHistoryEntry
	MAX-ACCESS	not-accessible
	STATUS	current
	DESCRIPTION
		""
::= { snmpTestObjects 3 }

messageHistoryEntry OBJECT-TYPE
	SYNTAX	MessageHistoryEntry
	MAX-ACCESS	not-accessible
	STATUS	current
	DESCRIPTION
		""

		INDEX	{
		IMPLIED index
		}
::= { messageHistoryTable 1 }

MessageHistoryEntry ::= SEQUENCE {
	index	DisplayString,
	element	DisplayString
}

index OBJECT-TYPE
	SYNTAX DisplayString
	ACCESS not-accessible
	STATUS current
	DESCRIPTION 
		""
::= { messageHistoryEntry 1 }

element OBJECT-TYPE
	SYNTAX DisplayString
	ACCESS read-write
	STATUS current
	DESCRIPTION 
		""
::= { messageHistoryEntry 2 }


messageHistoryAsArrayTable OBJECT-TYPE
	SYNTAX	SEQUENCE OF MessageHistoryAsArrayEntry
	MAX-ACCESS	not-accessible
	STATUS	current
	DESCRIPTION
		""
::= { snmpTestObjects 4 }

messageHistoryAsArrayEntry OBJECT-TYPE
	SYNTAX	MessageHistoryAsArrayEntry
	MAX-ACCESS	not-accessible
	STATUS	current
	DESCRIPTION
		""

		INDEX	{
		IMPLIED index
		}
::= { messageHistoryAsArrayTable 1 }

MessageHistoryAsArrayEntry ::= SEQUENCE {
	index	DisplayString,
	element	DisplayString
}

index OBJECT-TYPE
	SYNTAX DisplayString
	ACCESS not-accessible
	STATUS current
	DESCRIPTION 
		""
::= { messageHistoryAsArrayEntry 1 }

element OBJECT-TYPE
	SYNTAX DisplayString
	ACCESS read-write
	STATUS current
	DESCRIPTION 
		""
::= { messageHistoryAsArrayEntry 2 }


countHistoryTable OBJECT-TYPE
	SYNTAX	SEQUENCE OF CountHistoryEntry
	MAX-ACCESS	not-accessible
	STATUS	current
	DESCRIPTION
		""
::= { snmpTestObjects 5 }

countHistoryEntry OBJECT-TYPE
	SYNTAX	CountHistoryEntry
	MAX-ACCESS	not-accessible
	STATUS	current
	DESCRIPTION
		""

		INDEX	{
		IMPLIED index
		}
::= { countHistoryTable 1 }

CountHistoryEntry ::= SEQUENCE {
	index	DisplayString,
	element	DisplayString
}

index OBJECT-TYPE
	SYNTAX DisplayString
	ACCESS not-accessible
	STATUS current
	DESCRIPTION 
		""
::= { countHistoryEntry 1 }

element OBJECT-TYPE
	SYNTAX DisplayString
	ACCESS read-write
	STATUS current
	DESCRIPTION 
		""
::= { countHistoryEntry 2 }


messageCountHistoryTable OBJECT-TYPE
	SYNTAX	SEQUENCE OF MessageCountHistoryEntry
	MAX-ACCESS	not-accessible
	STATUS	current
	DESCRIPTION
		""
::= { snmpTestObjects 6 }

messageCountHistoryEntry OBJECT-TYPE
	SYNTAX	MessageCountHistoryEntry
	MAX-ACCESS	not-accessible
	STATUS	current
	DESCRIPTION
		""

		INDEX	{
		IMPLIED index
		}
::= { messageCountHistoryTable 1 }

MessageCountHistoryEntry ::= SEQUENCE {
	index	DisplayString,
	element	DisplayString
}

index OBJECT-TYPE
	SYNTAX DisplayString
	ACCESS not-accessible
	STATUS current
	DESCRIPTION 
		""
::= { messageCountHistoryEntry 1 }

element OBJECT-TYPE
	SYNTAX DisplayString
	ACCESS read-write
	STATUS current
	DESCRIPTION 
		""
::= { messageCountHistoryEntry 2 }


END
