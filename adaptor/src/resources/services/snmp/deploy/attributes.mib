--
-- Example MIB for the delivered attributes.xml
-- $Revision$
-- 

JBOSS-AS-MIB DEFINITIONS ::=BEGIN

-- Tree roots
org			OBJECT IDENTIFIER ::= { iso 2 } 
dod			OBJECT IDENTIFIER ::= { org 6 }
internet	OBJECT IDENTIFIER ::= { dod 1 }
private 	OBJECT IDENTIFIER ::= { internet 4 }  
enterprise 	OBJECT IDENTIFIER ::= { private 1 }
redhat		OBJECT IDENTIFIER ::= { enterprise 2312 }
jboss 		OBJECT IDENTIFIER ::= { redhat 100 }
as 			OBJECT IDENTIFIER ::= { jboss 1 }

-- system parameters
activeThreadCount OBJECT-TYPE
	SYNTAX INTEGER
	ACCESS read-only 
	STATUS mandatory
	DESCRIPTION
		"The number of active Threads in the system"
	::= { as 1 } 

freeMemory OBJECT-TYPE
	SYNTAX INTEGER
	ACCESS read-only
	STATUS mandatory
	DESCRIPTION
		"The free memory of the VM"
	::= { as 2 } 

maxMemory OBJECT-TYPE
	SYNTAX INTEGER
	ACCESS read-only
	STATUS mandatory
	DESCRIPTION
		"The max memory of the VM"
	::= { as 3} -- .1.2.3.4.1.3

threadPoolQueueSize OBJECT-TYPE
	SYNTAX INTEGER
	ACCESS read-only
	STATUS mandatory
	DESCRIPTION
		"The size of the thread pool queue"
	::= { as 4 }

requestCount8080 OBJECT-TYPE
	SYNTAX INTEGER
	ACCESS read-only
	STATUS mandatory
	DESCRIPTION
		"Number of requests served on port 8080"
	::= { as 5}

txCommitCount OBJECT-TYPE
	SYNTAX INTEGER
	ACCESS read-only
	STATUS mandatory
	DESCRIPTION
		"Number of commited transactions"
	::= { as 6 }

txRollbackCount OBJECT-TYPE
	SYNTAX INTEGER
	ACCESS read-only
	STATUS mandatory
	DESCRIPTION
		"Number of transactions rolled back"
	::= { as 7 }

txActiveCount OBJECT-TYPE
	SYNTAX INTEGER
	ACCESS read-only
	STATUS mandatory
	DESCRIPTION
		"The number of currently active transactions"
	::= { as 8 }

dbInUseCount OBJECT-TYPE
	SYNTAX INTEGER
	ACCESS read-only
	STATUS mandatory
	DESCRIPTION
		"The number of db connections currently in use"
	::= { as 9 }

END
