-- This MIB Generated by the JBoss MIB Generator

MSS-MIB DEFINITIONS ::=BEGIN

IMPORTS
	OBJECT-TYPE,
	NOTIFICATION-TYPE,
	Counter32,
	Gauge32,
	Counter64,
	TimeTicks
		FROM SNMPv2-SMI
	DisplayString,
	TruthValue
		FROM SNMPv2-TC;

jbossAsObjects		OBJECT IDENTIFIER ::= { 1 3 6 1 4 1 2312 100 1 1 }
webApplications		OBJECT IDENTIFIER ::= { 1 3 6 1 4 1 2312 100 1 1 }
system		OBJECT IDENTIFIER ::= { 1 3 6 1 2 1 1 }
sipStack		OBJECT IDENTIFIER ::= { 1 3 6 1 4 1 2312 100 1 1 20 1 }
jbossAsTraps		OBJECT IDENTIFIER ::= { 1 3 6 1 4 1 2312 100 1 2 0 }
sipApplicationDispatcher		OBJECT IDENTIFIER ::= { 1 3 6 1 4 1 2312 100 1 1 20 }

activeThreadCount OBJECT-TYPE
	SYNTAX INTEGER
	ACCESS read-only
	STATUS current
	DESCRIPTION 
		"The amount of active threads the server is handling."
::= { jbossAsObjects 1 }

freeMemory OBJECT-TYPE
	SYNTAX OCTET STRING (SIZE(0..255))
	ACCESS read-only
	STATUS current
	DESCRIPTION 
		"The amount of free memory on the server."
::= { jbossAsObjects 2 }

maxMemory OBJECT-TYPE
	SYNTAX OCTET STRING (SIZE(0..255))
	ACCESS read-only
	STATUS current
	DESCRIPTION 
		"The maximum usable amount of memory on the server."
::= { jbossAsObjects 3 }

instantiationTime OBJECT-TYPE
	SYNTAX DisplayString
	ACCESS read-only
	STATUS current
	DESCRIPTION 
		"The start time of the SNMP agent."
::= { jbossAsObjects 4 }

trapCount OBJECT-TYPE
	SYNTAX DisplayString
	ACCESS read-only
	STATUS current
	DESCRIPTION 
		"The number of traps emitted by the agent."
::= { jbossAsObjects 5 }

bindAddress OBJECT-TYPE
	SYNTAX DisplayString
	ACCESS read-only
	STATUS current
	DESCRIPTION 
		"The address to which the agent is bound."
::= { jbossAsObjects 6 }

inUseConnectionCount OBJECT-TYPE
	SYNTAX OCTET STRING (SIZE(0..255))
	ACCESS read-only
	STATUS current
	DESCRIPTION 
		"The amount of connections currently in use."
::= { jbossAsObjects 7 }

maxConnectionsInUseCount OBJECT-TYPE
	SYNTAX OCTET STRING (SIZE(0..255))
	ACCESS read-only
	STATUS current
	DESCRIPTION 
		"The maximum possible amount of connections available for use."
::= { jbossAsObjects 8 }

commitCount OBJECT-TYPE
	SYNTAX OCTET STRING (SIZE(0..255))
	ACCESS read-only
	STATUS current
	DESCRIPTION 
		""
::= { jbossAsObjects 9 }

rollbackCount OBJECT-TYPE
	SYNTAX OCTET STRING (SIZE(0..255))
	ACCESS read-only
	STATUS current
	DESCRIPTION 
		""
::= { jbossAsObjects 10 }

transactionCount OBJECT-TYPE
	SYNTAX OCTET STRING (SIZE(0..255))
	ACCESS read-only
	STATUS current
	DESCRIPTION 
		""
::= { jbossAsObjects 11 }

sysDescr OBJECT-TYPE
	SYNTAX OCTET STRING (SIZE(0..255))
	ACCESS read-write
	STATUS current
	DESCRIPTION 
		"A description of this System."
::= { system 1 }

sysObjectId OBJECT-TYPE
	SYNTAX OCTET STRING (SIZE(0..255))
	ACCESS read-only
	STATUS current
	DESCRIPTION 
		"The OID Denoting this system."
::= { system 2 }

sysUpTime OBJECT-TYPE
	SYNTAX OCTET STRING (SIZE(0..255))
	ACCESS read-only
	STATUS current
	DESCRIPTION 
		"The time this system has been online."
::= { system 3 }

sysContact OBJECT-TYPE
	SYNTAX OCTET STRING (SIZE(0..255))
	ACCESS read-only
	STATUS current
	DESCRIPTION 
		"The person who is admin to this system."
::= { system 4 }

sysName OBJECT-TYPE
	SYNTAX OCTET STRING (SIZE(0..255))
	ACCESS read-only
	STATUS current
	DESCRIPTION 
		"The name this system is known by."
::= { system 5 }

sysLocation OBJECT-TYPE
	SYNTAX OCTET STRING (SIZE(0..255))
	ACCESS read-only
	STATUS current
	DESCRIPTION 
		"The physical location of this system."
::= { system 6 }

sysServices OBJECT-TYPE
	SYNTAX OCTET STRING (SIZE(0..255))
	ACCESS read-only
	STATUS current
	DESCRIPTION 
		"The services provided by this system."
::= { system 7 }

baseTimerInterval OBJECT-TYPE
	SYNTAX INTEGER
	ACCESS read-write
	STATUS current
	DESCRIPTION 
		""
::= { sipApplicationDispatcher 2 }

t2Interval OBJECT-TYPE
	SYNTAX INTEGER
	ACCESS read-write
	STATUS current
	DESCRIPTION 
		""
::= { sipApplicationDispatcher 3 }

t4Interval OBJECT-TYPE
	SYNTAX INTEGER
	ACCESS read-write
	STATUS current
	DESCRIPTION 
		""
::= { sipApplicationDispatcher 4 }

timerDInterval OBJECT-TYPE
	SYNTAX INTEGER
	ACCESS read-write
	STATUS current
	DESCRIPTION 
		""
::= { sipApplicationDispatcher 5 }

congestionControlCheckingInterval OBJECT-TYPE
	SYNTAX INTEGER
	ACCESS read-write
	STATUS current
	DESCRIPTION 
		""
::= { sipApplicationDispatcher 6 }

memoryThreshold OBJECT-TYPE
	SYNTAX INTEGER
	ACCESS read-write
	STATUS current
	DESCRIPTION 
		""
::= { sipApplicationDispatcher 7 }

backToNormalMemoryThreshold OBJECT-TYPE
	SYNTAX INTEGER
	ACCESS read-write
	STATUS current
	DESCRIPTION 
		""
::= { sipApplicationDispatcher 8 }

gatherStatistics OBJECT-TYPE
	SYNTAX INTEGER
	ACCESS read-write
	STATUS current
	DESCRIPTION 
		""
::= { sipApplicationDispatcher 9 }

requestsProcessed OBJECT-TYPE
	SYNTAX OCTET STRING (SIZE(0..255))
	ACCESS read-only
	STATUS current
	DESCRIPTION 
		""
::= { sipApplicationDispatcher 10 }

responsesProcessed OBJECT-TYPE
	SYNTAX OCTET STRING (SIZE(0..255))
	ACCESS read-only
	STATUS current
	DESCRIPTION 
		""
::= { sipApplicationDispatcher 11 }

numberOfClientTransactions OBJECT-TYPE
	SYNTAX INTEGER
	ACCESS read-only
	STATUS current
	DESCRIPTION 
		""
::= { sipStack 1 }

numberOfServerTransactions OBJECT-TYPE
	SYNTAX INTEGER
	ACCESS read-only
	STATUS current
	DESCRIPTION 
		""
::= { sipStack 2 }

numberOfDialogs OBJECT-TYPE
	SYNTAX INTEGER
	ACCESS read-only
	STATUS current
	DESCRIPTION 
		""
::= { sipStack 3 }

localMode OBJECT-TYPE
	SYNTAX INTEGER
	ACCESS read-only
	STATUS current
	DESCRIPTION 
		""
::= { sipStack 4 }

jbossJmxNotificationMessage OBJECT-TYPE
	SYNTAX DisplayString
	ACCESS not-accessible
	STATUS current
	DESCRIPTION 
		""
::= { jbossAsObjects 30 }

jbossJmxNotificationSequenceNumber OBJECT-TYPE
	SYNTAX DisplayString
	ACCESS not-accessible
	STATUS current
	DESCRIPTION 
		""
::= { jbossAsObjects 31 }

jbossJmxNotificationMessage OBJECT-TYPE
	SYNTAX DisplayString
	ACCESS not-accessible
	STATUS current
	DESCRIPTION 
		""
::= { jbossAsObjects 1000 }

jbossAsHeartbeatNotification NOTIFICATION-TYPE
	OBJECTS {
		sysUpTime,
		trapCount,
		jbossJmxNotificationMessage,
		jbossJmxNotificationSequenceNumber
		}
	STATUS current
	DESCRIPTION 
		""
::= { jbossAsTraps 3 }

jbossAsColdstartNotification NOTIFICATION-TYPE
	OBJECTS {
		instantiationTime,
		trapCount
		}
	STATUS current
	DESCRIPTION 
		""
::= { jbossAsTraps 1 }

jbossAsClusterViewChangedNotification NOTIFICATION-TYPE
	OBJECTS {
		instantiationTime,
		trapCount,
		jbossJmxNotificationMessage
		}
	STATUS current
	DESCRIPTION 
		""
::= { jbossAsTraps 0 }

requestsProcessedByMethodTable OBJECT-TYPE
	SYNTAX	SEQUENCE OF RequestsProcessedByMethodEntry
	MAX-ACCESS	not-accessible
	STATUS	current
	DESCRIPTION
		""
::= { sipApplicationDispatcher 12 }

requestsProcessedByMethodEntry OBJECT-TYPE
	SYNTAX	RequestsProcessedByMethodEntry
	MAX-ACCESS	not-accessible
	STATUS	current
	DESCRIPTION
		""

		INDEX	{
		IMPLIED index
		}
::= { requestsProcessedByMethodTable 1 }

RequestsProcessedByMethodEntry ::= SEQUENCE {
	index	DisplayString,
	element	DisplayString
}

index OBJECT-TYPE
	SYNTAX DisplayString
	ACCESS not-accessible
	STATUS current
	DESCRIPTION 
		""
::= { requestsProcessedByMethodEntry 1 }

element OBJECT-TYPE
	SYNTAX DisplayString
	ACCESS read-only
	STATUS current
	DESCRIPTION 
		""
::= { requestsProcessedByMethodEntry 2 }


responsesProcessedByStatusCodeTable OBJECT-TYPE
	SYNTAX	SEQUENCE OF ResponsesProcessedByStatusCodeEntry
	MAX-ACCESS	not-accessible
	STATUS	current
	DESCRIPTION
		""
::= { sipApplicationDispatcher 13 }

responsesProcessedByStatusCodeEntry OBJECT-TYPE
	SYNTAX	ResponsesProcessedByStatusCodeEntry
	MAX-ACCESS	not-accessible
	STATUS	current
	DESCRIPTION
		""

		INDEX	{
		IMPLIED index
		}
::= { responsesProcessedByStatusCodeTable 1 }

ResponsesProcessedByStatusCodeEntry ::= SEQUENCE {
	index	DisplayString,
	element	DisplayString
}

index OBJECT-TYPE
	SYNTAX DisplayString
	ACCESS not-accessible
	STATUS current
	DESCRIPTION 
		""
::= { responsesProcessedByStatusCodeEntry 1 }

element OBJECT-TYPE
	SYNTAX DisplayString
	ACCESS read-only
	STATUS current
	DESCRIPTION 
		""
::= { responsesProcessedByStatusCodeEntry 2 }


metricsTable OBJECT-TYPE
	SYNTAX	SEQUENCE OF MetricsEntry
	MAX-ACCESS	not-accessible
	STATUS	current
	DESCRIPTION
		"Table containing standard metrics for any webapp deployed on JBossAS"
::= { webApplications 12 }

metricsEntry OBJECT-TYPE
	SYNTAX	MetricsEntry
	MAX-ACCESS	not-accessible
	STATUS	current
	DESCRIPTION
		""

		INDEX	{
		IMPLIED metricsObjectName
		}
::= { metricsTable 1 }

MetricsEntry ::= SEQUENCE {
	metricsObjectName	DisplayString,
	metricsDistributable	INTEGER,
	metricsSessionCounter	INTEGER,
	metricsActiveSessions	INTEGER,
	metricsMaxActiveSessions	INTEGER,
	metricsSessionAverageAliveTime	INTEGER,
	metricsExpiredSessions	INTEGER,
	metricsRejectedSessions	INTEGER,
	metricsMaxInactiveInterval	INTEGER,
	metricsSessionMaxAliveTime	INTEGER
}

metricsObjectName OBJECT-TYPE
	SYNTAX DisplayString
	ACCESS not-accessible
	STATUS current
	DESCRIPTION 
		""
::= { metricsEntry 1 }

metricsDistributable OBJECT-TYPE
	SYNTAX INTEGER
	ACCESS read-only
	STATUS current
	DESCRIPTION 
		""
::= { metricsEntry 2 }

metricsSessionCounter OBJECT-TYPE
	SYNTAX INTEGER
	ACCESS read-only
	STATUS current
	DESCRIPTION 
		"The amount of sessions this web application has handled."
::= { metricsEntry 3 }

metricsActiveSessions OBJECT-TYPE
	SYNTAX INTEGER
	ACCESS read-only
	STATUS current
	DESCRIPTION 
		"The amount of currently active sessions this web application is handling."
::= { metricsEntry 4 }

metricsMaxActiveSessions OBJECT-TYPE
	SYNTAX INTEGER
	ACCESS read-write
	STATUS current
	DESCRIPTION 
		"The maximum amount of active sessions this web application can handle at once."
::= { metricsEntry 5 }

metricsSessionAverageAliveTime OBJECT-TYPE
	SYNTAX INTEGER
	ACCESS read-only
	STATUS current
	DESCRIPTION 
		"The average time a session is active on this web application."
::= { metricsEntry 6 }

metricsExpiredSessions OBJECT-TYPE
	SYNTAX INTEGER
	ACCESS read-only
	STATUS current
	DESCRIPTION 
		"The amount of expired sessions related to this web application."
::= { metricsEntry 7 }

metricsRejectedSessions OBJECT-TYPE
	SYNTAX INTEGER
	ACCESS read-only
	STATUS current
	DESCRIPTION 
		"The amount of rejected sessions related to this web application."
::= { metricsEntry 8 }

metricsMaxInactiveInterval OBJECT-TYPE
	SYNTAX INTEGER
	ACCESS read-only
	STATUS current
	DESCRIPTION 
		"The amount of time that must expire before a session is considered inactive."
::= { metricsEntry 9 }

metricsSessionMaxAliveTime OBJECT-TYPE
	SYNTAX INTEGER
	ACCESS read-only
	STATUS current
	DESCRIPTION 
		"The maximum amount of time a session can remain active."
::= { metricsEntry 10 }


sipMetricsTable OBJECT-TYPE
	SYNTAX	SEQUENCE OF SipMetricsEntry
	MAX-ACCESS	not-accessible
	STATUS	current
	DESCRIPTION
		"Table containing standard metrics for any webapp deployed on JBossAS"
::= { webApplications 13 }

sipMetricsEntry OBJECT-TYPE
	SYNTAX	SipMetricsEntry
	MAX-ACCESS	not-accessible
	STATUS	current
	DESCRIPTION
		""

		INDEX	{
		IMPLIED sipMetricsObjectName
		}
::= { sipMetricsTable 1 }

SipMetricsEntry ::= SEQUENCE {
	sipMetricsObjectName	DisplayString,
	sipMetricsDistributable	INTEGER,
	sipMetricsSessionCounter	INTEGER,
	sipMetricsActiveSessions	INTEGER,
	sipMetricsMaxActiveSessions	INTEGER,
	sipMetricsSessionAverageAliveTime	INTEGER,
	sipMetricsExpiredSessions	INTEGER,
	sipMetricsRejectedSessions	INTEGER,
	sipMetricsMaxInactiveInterval	INTEGER,
	sipMetricsSessionMaxAliveTime	INTEGER,
	sipMetricsSipSessionCounter	INTEGER,
	sipMetricsSipApplicationSessionCounter	INTEGER,
	sipMetricsActiveSipSessions	INTEGER,
	sipMetricsActiveSipApplicationSessions	INTEGER,
	sipMetricsExpiredSipSessions	INTEGER,
	sipMetricsExpiredSipApplicationSessions	INTEGER,
	sipMetricsRejectedSipSessions	INTEGER,
	sipMetricsRejectedSipApplicationSessions	INTEGER,
	sipMetricsMaxActiveSipSessions	INTEGER,
	sipMetricsMaxActiveSipApplicationSessions	INTEGER,
	sipMetricsSipSessionAverageAliveTime	INTEGER,
	sipMetricsSipApplicationSessionAverageAliveTime	INTEGER,
	sipMetricsSipSessionMaxAliveTime	INTEGER,
	sipMetricsSipApplicationSessionMaxAliveTime	INTEGER,
	sipMetricsNumberOfSipSessionCreationPerSecond	INTEGER,
	sipMetricsNumberOfSipApplicationSessionCreationPerSecond	INTEGER
}

sipMetricsObjectName OBJECT-TYPE
	SYNTAX DisplayString
	ACCESS not-accessible
	STATUS current
	DESCRIPTION 
		""
::= { sipMetricsEntry 1 }

sipMetricsDistributable OBJECT-TYPE
	SYNTAX INTEGER
	ACCESS read-only
	STATUS current
	DESCRIPTION 
		""
::= { sipMetricsEntry 2 }

sipMetricsSessionCounter OBJECT-TYPE
	SYNTAX INTEGER
	ACCESS read-only
	STATUS current
	DESCRIPTION 
		"The amount of sessions this web application has handled."
::= { sipMetricsEntry 3 }

sipMetricsActiveSessions OBJECT-TYPE
	SYNTAX INTEGER
	ACCESS read-only
	STATUS current
	DESCRIPTION 
		"The amount of currently active sessions this web application is handling."
::= { sipMetricsEntry 4 }

sipMetricsMaxActiveSessions OBJECT-TYPE
	SYNTAX INTEGER
	ACCESS read-write
	STATUS current
	DESCRIPTION 
		"The maximum amount of active sessions this web application can handle at once."
::= { sipMetricsEntry 5 }

sipMetricsSessionAverageAliveTime OBJECT-TYPE
	SYNTAX INTEGER
	ACCESS read-only
	STATUS current
	DESCRIPTION 
		"The average time a session is active on this web application."
::= { sipMetricsEntry 6 }

sipMetricsExpiredSessions OBJECT-TYPE
	SYNTAX INTEGER
	ACCESS read-only
	STATUS current
	DESCRIPTION 
		"The amount of expired sessions related to this web application."
::= { sipMetricsEntry 7 }

sipMetricsRejectedSessions OBJECT-TYPE
	SYNTAX INTEGER
	ACCESS read-only
	STATUS current
	DESCRIPTION 
		"The amount of rejected sessions related to this web application."
::= { sipMetricsEntry 8 }

sipMetricsMaxInactiveInterval OBJECT-TYPE
	SYNTAX INTEGER
	ACCESS read-only
	STATUS current
	DESCRIPTION 
		"The amount of time that must expire before a session is considered inactive."
::= { sipMetricsEntry 9 }

sipMetricsSessionMaxAliveTime OBJECT-TYPE
	SYNTAX INTEGER
	ACCESS read-only
	STATUS current
	DESCRIPTION 
		"The maximum amount of time a session can remain active."
::= { sipMetricsEntry 10 }

sipMetricsSipSessionCounter OBJECT-TYPE
	SYNTAX INTEGER
	ACCESS read-only
	STATUS current
	DESCRIPTION 
		"The amount of sip sessions this web application has handled."
::= { sipMetricsEntry 11 }

sipMetricsSipApplicationSessionCounter OBJECT-TYPE
	SYNTAX INTEGER
	ACCESS read-only
	STATUS current
	DESCRIPTION 
		"The amount of sip application sessions this web application has handled."
::= { sipMetricsEntry 12 }

sipMetricsActiveSipSessions OBJECT-TYPE
	SYNTAX INTEGER
	ACCESS read-only
	STATUS current
	DESCRIPTION 
		"The amount of currently active sip sessions this web application is handling."
::= { sipMetricsEntry 13 }

sipMetricsActiveSipApplicationSessions OBJECT-TYPE
	SYNTAX INTEGER
	ACCESS read-only
	STATUS current
	DESCRIPTION 
		"The amount of currently active sip application sessions this web application is handling."
::= { sipMetricsEntry 14 }

sipMetricsExpiredSipSessions OBJECT-TYPE
	SYNTAX INTEGER
	ACCESS read-only
	STATUS current
	DESCRIPTION 
		"The amount of expired sip sessions related to this web application."
::= { sipMetricsEntry 15 }

sipMetricsExpiredSipApplicationSessions OBJECT-TYPE
	SYNTAX INTEGER
	ACCESS read-only
	STATUS current
	DESCRIPTION 
		"The amount of expired sip application sessions related to this web application."
::= { sipMetricsEntry 16 }

sipMetricsRejectedSipSessions OBJECT-TYPE
	SYNTAX INTEGER
	ACCESS read-only
	STATUS current
	DESCRIPTION 
		"The amount of rejected sip sessions related to this web application."
::= { sipMetricsEntry 17 }

sipMetricsRejectedSipApplicationSessions OBJECT-TYPE
	SYNTAX INTEGER
	ACCESS read-only
	STATUS current
	DESCRIPTION 
		"The amount of rejected sip application sessions related to this web application."
::= { sipMetricsEntry 18 }

sipMetricsMaxActiveSipSessions OBJECT-TYPE
	SYNTAX INTEGER
	ACCESS read-write
	STATUS current
	DESCRIPTION 
		"The maximum amount of active sip sessions this web application can handle at once."
::= { sipMetricsEntry 19 }

sipMetricsMaxActiveSipApplicationSessions OBJECT-TYPE
	SYNTAX INTEGER
	ACCESS read-write
	STATUS current
	DESCRIPTION 
		"The maximum amount of active sip application sessions this web application can handle at once."
::= { sipMetricsEntry 20 }

sipMetricsSipSessionAverageAliveTime OBJECT-TYPE
	SYNTAX INTEGER
	ACCESS read-only
	STATUS current
	DESCRIPTION 
		"The average time a sip session is active on this web application."
::= { sipMetricsEntry 21 }

sipMetricsSipApplicationSessionAverageAliveTime OBJECT-TYPE
	SYNTAX INTEGER
	ACCESS read-only
	STATUS current
	DESCRIPTION 
		"The average time a sip application session is active on this web application."
::= { sipMetricsEntry 22 }

sipMetricsSipSessionMaxAliveTime OBJECT-TYPE
	SYNTAX INTEGER
	ACCESS read-only
	STATUS current
	DESCRIPTION 
		"The maximum amount of time a sip session can remain active."
::= { sipMetricsEntry 23 }

sipMetricsSipApplicationSessionMaxAliveTime OBJECT-TYPE
	SYNTAX INTEGER
	ACCESS read-only
	STATUS current
	DESCRIPTION 
		"The maximum amount of time a sip application session can remain active."
::= { sipMetricsEntry 24 }

sipMetricsNumberOfSipSessionCreationPerSecond OBJECT-TYPE
	SYNTAX INTEGER
	ACCESS read-only
	STATUS current
	DESCRIPTION 
		"The number of sip session created per second."
::= { sipMetricsEntry 25 }

sipMetricsNumberOfSipApplicationSessionCreationPerSecond OBJECT-TYPE
	SYNTAX INTEGER
	ACCESS read-only
	STATUS current
	DESCRIPTION 
		"The number of sip application session created per second."
::= { sipMetricsEntry 26 }


END
