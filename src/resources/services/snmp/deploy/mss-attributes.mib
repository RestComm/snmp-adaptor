--
-- Example MIB for the delivered attributes.xml
-- $Revision: 44604 $
-- 

JBOSS-AS-MIB DEFINITIONS ::=BEGIN

-- Tree roots
org			OBJECT IDENTIFIER ::= { iso 2 } 
dod			OBJECT IDENTIFIER ::= { org 6 }
internet	OBJECT IDENTIFIER ::= { dod 1 }
private 	OBJECT IDENTIFIER ::= { internet 4 }  
enterprise 	OBJECT IDENTIFIER ::= { private 1 }
redhat		OBJECT IDENTIFIER ::= { enterprise 2312 }
jboss 		OBJECT IDENTIFIER ::= { redhat 100 }
as 			OBJECT IDENTIFIER ::= { jboss 1 }
web			OBJECT IDENTIFIER ::= { as 1 }
sip			OBJECT IDENTIFIER ::= { as 11 }
stack		OBJECT IDENTIFIER ::= { sip 1 }

-- system parameters
activeThreadCount OBJECT-TYPE
	SYNTAX INTEGER
	ACCESS read-only 
	STATUS mandatory
	DESCRIPTION
		"The number of active Threads in the system"
	::= { jboss 1 } 

freeMemory OBJECT-TYPE
	SYNTAX INTEGER
	ACCESS read-only
	STATUS mandatory
	DESCRIPTION
		"The free memory of the VM"
	::= { jboss 2 } 

maxMemory OBJECT-TYPE
	SYNTAX INTEGER
	ACCESS read-only
	STATUS mandatory
	DESCRIPTION
		"The max memory of the VM"
	::= {jboss 3} -- .1.2.3.4.1.3

threadPoolQueueSize OBJECT-TYPE
	SYNTAX INTEGER
	ACCESS read-only
	STATUS mandatory
	DESCRIPTION
		"The size of the thread pool queue"
	::= {jboss 4 }

requestCount8080 OBJECT-TYPE
	SYNTAX INTEGER
	ACCESS read-only
	STATUS mandatory
	DESCRIPTION
		"Number of requests served on port 8080"
	::= {jboss 5}

txCommitCount OBJECT-TYPE
	SYNTAX INTEGER
	ACCESS read-only
	STATUS mandatory
	DESCRIPTION
		"Number of commited transactions"
	::= {jboss 6 }

txRollbackCount OBJECT-TYPE
	SYNTAX INTEGER
	ACCESS read-only
	STATUS mandatory
	DESCRIPTION
		"Number of transactions rolled back"
	::= {jboss 7 }

txActiveCount OBJECT-TYPE
	SYNTAX INTEGER
	ACCESS read-only
	STATUS mandatory
	DESCRIPTION
		"The number of currently active transactions"
	::= {jboss 8 }

dbInUseCount OBJECT-TYPE
	SYNTAX INTEGER
	ACCESS read-only
	STATUS mandatory
	DESCRIPTION
		"The number of db connections currently in use"
	::= { jboss 9 }
	
-- sip attributes
baseTimerInterval OBJECT-TYPE
	SYNTAX INTEGER
	ACCESS read-write
	STATUS current
	DESCRIPTION
		"JAIN SIP Timer Interval"
	::= {sip 2}
t2Interval OBJECT-TYPE
	SYNTAX INTEGER
	ACCESS read-write
	STATUS current
	DESCRIPTION
		"JAIN SIP T2 Interval"
	::= {sip 3}
t4Interval OBJECT-TYPE
	SYNTAX INTEGER
	ACCESS read-write
	STATUS current
	DESCRIPTION
		"JAIN SIP T4 Interval"
	::= {sip 4}
timerDInterval OBJECT-TYPE
	SYNTAX INTEGER
	ACCESS read-write
	STATUS current
	DESCRIPTION
		"JAIN SIP Timer D Interval"
	::= {sip 5}
memoryThreshold OBJECT-TYPE
	SYNTAX INTEGER
	ACCESS read-write
	STATUS current
	DESCRIPTION
		"JAIN SIP Timer D Interval"
	::= {sip 6}
backToNormalMemoryThreshold OBJECT-TYPE
	SYNTAX INTEGER
	ACCESS read-write
	STATUS current
	DESCRIPTION
		"JAIN SIP Timer D Interval"
	::= {sip 7}
gatherStatistics  OBJECT-TYPE
	SYNTAX INTEGER
	ACCESS read-write
	STATUS current
	DESCRIPTION
		"JAIN SIP Timer D Interval"
	::= {sip 8}
requestsProcessed  OBJECT-TYPE
	SYNTAX INTEGER
	ACCESS read-only
	STATUS current
	DESCRIPTION
		"number of requests processed by the sip application dispatcher"
	::= {sip 9}
responsesProcessed  OBJECT-TYPE
	SYNTAX INTEGER
	ACCESS read-only
	STATUS current
	DESCRIPTION
		"number of responses processed by the sip application dispatcher"
	::= {sip 10}
congestionControlCheckingInterval OBJECT-TYPE
	SYNTAX INTEGER
	ACCESS read-write
	STATUS current
	DESCRIPTION
		"Congestion control interval specifies at which interval (in millisecs) runs the statistics for congestion control"
	::= {sip 11}
numberOfClientTransactions OBJECT-TYPE
	SYNTAX INTEGER
	ACCESS read-only
	STATUS current
	DESCRIPTION
		"Number of active Client Transactions"
	::= {stack 1}
numberOfServerTransactions OBJECT-TYPE
	SYNTAX INTEGER
	ACCESS read-only
	STATUS current
	DESCRIPTION
		"Number of active Server Transactions"
	::= {stack 2}
numberOfDialogs OBJECT-TYPE
	SYNTAX INTEGER
	ACCESS read-only
	STATUS current
	DESCRIPTION
		"Number of active dialogs"
	::= {stack 3}
localMode OBJECT-TYPE
	SYNTAX INTEGER
	ACCESS read-only
	STATUS current
	DESCRIPTION
		"Is the stack runnning in distributed or local mode"
	::= {stack 4}
END
